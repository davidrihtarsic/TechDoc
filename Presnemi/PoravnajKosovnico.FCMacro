names     = ["POZ.", "KOS", "NAZIV IN MERE KOSA", "ŠT. RISBE/STD.", "MATERIAL", "MASA" ]
cells     = ["A", "B", "C", "D", "E", "F"]
widths_mm = [7.3, 7.3, 64.8, 55.1, 25.1, 25]

widths_px = [0, 0, 0, 0, 0, 0]
DPI = 96

for i in range(len(cells)):
    widths_px[i] = int(round(widths_mm[i]/25.4 * DPI))

for i in range(len(cells)):
    App.ActiveDocument.Spreadsheet.setColumnWidth(cells[i], widths_px[i])
    App.ActiveDocument.Spreadsheet.set(cells[i]+"1", names[i])
    App.ActiveDocument.Spreadsheet.setAlignment(cells[i]+"1", 'center', 'keep')

App.ActiveDocument.recompute()
